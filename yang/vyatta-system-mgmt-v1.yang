module vyatta-system-mgmt-v1 {
	namespace "urn:vyatta.com:mgmt:vyatta-system-mgmt:1";
	prefix vyatta-system-mgmt-v1;

	import vyatta-system-v1 {
		prefix system;
	}
	import configd-v1 {
		prefix configd;
	}

	organization "AT&T Inc.";
	contact
		"AT&T
		 Postal: 208 S. Akard Street
		         Dallas, TX 75202
		 Web: www.att.com";

	description
		"Copyright (c) 2019 AT&T Intellectual Property
		 All rights reserved.

		 Copyright (c) 2014-2016 by Brocade Communications Systems, Inc.
		 All rights reserved.

		 Redistribution and use in source and binary forms, with or without
		 modification, are permitted provided that the following conditions
		 are met:

		 1. Redistributions of source code must retain the above copyright
		    notice, this list of conditions and the following disclaimer.
		 2. Redistributions in binary form must reproduce the above
		    copyright notice, this list of conditions and the following
		    disclaimer in the documentation and/or other materials provided
		    with the distribution.
		 3. Neither the name of the copyright holder nor the names of its
		    contributors may be used to endorse or promote products derived
		    from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 The YANG module for vyatta-system-mgmt-v1";

	revision 2019-06-24 {
		description "Update organization and contact details. 
			Deprecate commit-archive location.
			Add archive-location, with separate username and
			password to allow passwords to be made secret";
	}

	revision 2016-03-17 {
		description "Move commit-archive to grouping.";
	}
	revision 2015-12-04 {
		description "Convert comp_help extension to description.";
	}
	revision 2015-08-14 {
		description "Initial revision of version 1.";
	}
	
	grouping cfg-mgt-commit-archive-group {
		container commit-archive {
			presence
			  "Enables config commit archive to remote locations";
			description "Remote locations for archived config commit";
			configd:priority "400";
			configd:help "Commit archival settings";
			configd:end "/opt/vyatta/share/tmplscripts/system/config-management/commit-archive/configd_end.sh";
			list archive {
				description "Location of commit archive";
				configd:help "Commit archive locations";
				key url;

				leaf url {
					description "Location of commit archive

					     URLs supported are:
					      - scp://<host>/<dir>
					      - ftp://<host>/<dir>
					      - tftp://<host>/<dir>";
					type string {
						pattern '(tftp|ftp|scp)://.*/.*' {
							error-message "URL scheme must one of tftp, ftp, scp";
						}
					}
				}


				leaf username {
					description "Username for archive location authentication";
					configd:help "Username for archive authentication";
					type string;
				}

				leaf password {
					description "Password for archive location authentication";
					configd:help "Password for archive authentication";
					configd:secret true;
					type string;
				}
			}

			leaf-list location {
				status deprecated;
				description "Location of commit archive

					     URLs supported are:
					      - scp://<user>:<passwd>@<host>/<dir>
					      - ftp://<user>:<passwd>@<host>/<dir>
					      - tftp://<host>/<dir>";
				type string {
					pattern '(tftp|ftp|scp)://.*/.*' {
						error-message "URL scheme must one of tftp, ftp, scp";
					}
				}
				ordered-by "user";
				configd:help "Commit archive location";
			}
		}
	}

	augment /system:system {
		container config-management {
			presence "true";
			configd:help "Configuration management settings";
			uses cfg-mgt-commit-archive-group;
			leaf commit-revisions {
				type uint32 {
					range 0..65535 {
						error-message "Commit revisions must be in range 0 to 65535";
					}
				}
				configd:priority "400";
				configd:help "Commit revisions";
				configd:update "/opt/vyatta/share/tmplscripts/system/config-management/commit-revisions/configd_update.sh";
				configd:delete "/opt/vyatta/share/tmplscripts/system/config-management/commit-revisions/configd_delete.sh";
			}
		}
	}
}
